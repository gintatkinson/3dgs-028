module ietf-ni-location {
  yang-version 1.1;
  namespace "urn:ietf:params:xml:ns:yang:ietf-ni-location";
  prefix nil;

  import ietf-yang-types {
    prefix yang;
    reference
      "RFC 9911: Common YANG Data Types";
  }
  import ietf-network-inventory {
    prefix nwi;
    reference
      "RFCAAAA: A YANG Data Model for Network Inventory";
  }
  import ietf-geo-location {
    prefix geo;
    reference
      "RFC 9179: A YANG Grouping for Geographic Locations";
  }

  organization
    "IETF Network Inventory YANG (ivy) Working Group";
  contact
    "WG Web:   <https://datatracker.ietf.org/wg/ivy>
     WG List:  <mailto:inventory-yang@ietf.org>

     Editor: Bo Wu
          <lana.wubo@huawei.com>
     Editor: Sergio Belotti
          <sergio.belotti@nokia.com>
     Editor: Jean-Francois Bouquier
          <jeff.bouquier@vodafone.com>
     Editor: Fabio Peruzzini
          <fabio.peruzzini@telecomitalia.it>
     Editor: Phil Bedard
          <phbedard@cisco.com>";
  description
    "This YANG module defines a model for Network Inventory
     location.

     Copyright (c) 2026 IETF Trust and the persons
     identified as authors of the code.  All rights reserved.

     Redistribution and use in source and binary forms, with or
     without modification, is permitted pursuant to, and subject
     to the license terms contained in, the Revised BSD License
     set forth in Section 4.c of the IETF Trust's Legal Provisions
     Relating to IETF Documents
     (https://trustee.ietf.org/license-info).

     This version of this YANG module is part of RFC XXXX; see
     the RFC itself for full legal notices.";

  revision 2026-07-06 {
    description
      "Initial version";
    reference
      "RFC XXXX: A YANG Data Model for Network Inventory location.";
  }

  /* Identities for rack classification */

  identity rack-class-type {
    description
      "Base identity for generic rack classification based on
       physical security characteristics.
       This identity is designed to be extended by regional
       or vendor-specific rack classes.";
  }

  identity rack-standard {
    base rack-class-type;
    description
      "Standard general-purpose rack without physical locking
       mechanisms.";
  }

  identity rack-secure-baseline {
    base rack-class-type;
    description
      "Baseline secure lockable rack.";
  }

  identity rack-secure-medium {
    base rack-class-type;
    description
      "Medium security lockable rack.";
  }

  identity rack-secure-high {
    base rack-class-type;
    description
      "High security lockable rack.";
  }

  /* Typedef */

  typedef ni-location-ref {
    type leafref {
      path "/nwi:network-inventory/nil:locations/nil:location"
         + "/nil:id";
    }
    description
      "This type is used by data models that need to reference
       network inventory location.";
  }

  /* Grouping */

  grouping physical-address {
    description
      "Grouping for physical address information.";
    container physical-address {
      description
        "Top-level container for the physical address.";
      leaf address {
        type string;
        description
          "Specifies an address (number and street).";
      }
      leaf postal-code {
        type string;
        description
          "Specifies a postal code.";
      }
      leaf state {
        type string;
        description
          "Specifies a state. This leaf can also be
           used to describe a region for a country that
           does not have states.";
      }
      leaf city {
        type string;
        description
          "Specifies a city.";
      }
      leaf country-code {
        type string {
          pattern '[A-Z]{2}';
        }
        description
          "Specifies a country.
           Expressed as ISO ALPHA-2 code.";
      }
    }
  }

  grouping locations {
    description
      "Grouping for locations.";
    container locations {
      config false;
      description
        "Container for the location information.";
      list location {
        key "id";
        description
          "List of locations within the network.";
        leaf id {
          type string;
          description
            "An identifier of the location.";
        }
        uses nwi:basic-common-entity-attributes;
        leaf type {
          type string;
          description
            "The type of network inventory location, e.g.
             equipment room, building, or site.
             This allows operators to flexibly define custom location
             types (e.g., 'pole', 'roof', 'floor') based on their
             specific network scenarios without requiring model
             extensions. String-based types enable dynamic adaptation
             to heterogeneous organizational naming conventions.";
        }
        leaf parent {
          type leafref {
            path "../../location/id";
          }
          description
            "The identifier of the location that physically contains
             this location.";
        }
        leaf timestamp {
          type yang:date-and-time;
          description
            "Timestamp when the location was recorded.";
        }
        leaf valid-until {
          type yang:date-and-time;
          description
            "The timestamp for which this location is valid until.
             If unspecified, the location has no specific
             expiration time.";
        }
        uses physical-address;
        uses geo:geo-location;
        list contained-chassis {
          key "chassis-id";
          description
            "Chassis directly deployed in this location without rack.
             Also used for distributed chassis components that are
             logically part of a network element but physically
             located.";
          leaf chassis-id {
            type uint32;
            description
              "Unique identifier for this chassis instance in the
               location.";
          }
          leaf ne-ref {
            type leafref {
              path "/nwi:network-inventory/nwi:network-elements"
                 + "/nwi:network-element/nwi:ne-id";
            }
            description
              "Reference to the network element this chassis
               belongs to. Multiple chassis entries may reference
               the same ne-ref for distributed systems.";
          }
          leaf component-ref {
            type leafref {
              path
                "/nwi:network-inventory/nwi:network-elements"
              + "/nwi:network-element[nwi:ne-id=current()/../ne-ref]"
              + "/nwi:components/nwi:component/nwi:component-id";
            }
            description
              "Reference to the specific chassis within the
               network element.";
          }
        }
      }
      uses racks;
    }
  }

  grouping racks {
    description
      "Grouping for rack attributes.";
    container racks {
      config false;
      description
        "Top-level container for the list of racks.";
      list rack {
        key "id";
        description
          "List of racks within the inventory (e.g., in an
           equipment room).";
        leaf id {
          type string;
          description
            "An identifier that uniquely identifies the rack.";
        }
        leaf rack-class {
          type identityref {
            base rack-class-type;
          }
          description
            "Classification of the rack.";
        }
        uses nwi:basic-common-entity-attributes;
        container rack-location {
          description
            "The location information of the rack, which comprises
             the location reference, row number, and column number.";
          leaf location-ref {
            type ni-location-ref;
            description
              "Reference to the location where this rack is placed.";
          }
          leaf row-number {
            type uint32;
            description
              "Identifies the row within the location where
               the rack is located.";
          }
          leaf column-number {
            type uint32;
            description
              "Identifies the column within the location where
               the rack is located.";
          }
        }
        leaf height {
          type uint16;
          units "millimeter";
          description
            "Rack height.";
        }
        leaf width {
          type uint16;
          units "millimeter";
          description
            "Rack width.";
        }
        leaf depth {
          type uint16;
          units "millimeter";
          description
            "Rack depth.";
        }
        leaf max-voltage {
          type uint16;
          units "volt";
          description
            "The maximum voltage supported by the rack.";
        }
        leaf max-allocated-power {
          type uint16;
          units "watts";
          description
            "The maximum allocated power for the rack.";
        }
        list contained-chassis {
          key "relative-position";
          description
            "The list of chassis within a rack.";
          leaf relative-position {
            type uint8;
            description
              "Relative position (e.g., U-slot) of chassis within
               the rack.";
          }
          leaf ne-ref {
            type leafref {
              path "/nwi:network-inventory/nwi:network-elements"
                 + "/nwi:network-element/nwi:ne-id";
            }
            description
              "Reference to the network element containing
               the chassis component.";
          }
          leaf component-ref {
            type leafref {
              path "/nwi:network-inventory/nwi:network-elements"
                 + "/nwi:network-element[nwi:ne-id=current()/.."
                 + "/ne-ref]/nwi:components/nwi:component"
                 + "/nwi:component-id";
            }
            description
              "The reference to the chassis component within
               the network element and contained by the rack.";
          }
        }
        leaf timestamp {
          type yang:date-and-time;
          description
            "Timestamp when the rack information was recorded.";
        }
        leaf valid-until {
          type yang:date-and-time;
          description
            "The timestamp for which this rack is valid until.
             If unspecified, the rack has no specific
             expiration time.";
        }
      }
    }
  }

  augment "/nwi:network-inventory" {
    description
      "Provides location information for network inventory.";
    uses locations;
  }
}
